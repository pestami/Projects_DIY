import math

nSIZE=10
sNAME='ShapeString'
fRadius=130
X0=150 -nSIZE*0.8
Y0=150 -nSIZE*0.8

FreeCAD.ActiveDocument.getObject(sNAME).Size=nSIZE

#-------------------------------------------------------------------
for i in range(1, 25):

	if (i>16):
		nSIZE_LASER=nSIZE*0.8
	else:
		nSIZE_LASER=nSIZE

	angle_deg=-90 - (i-1)*15
	angle=angle_deg/180*3.14

	X=X0 + fRadius * math.cos(angle) - nSIZE* math.cos(angle) 
	Y=Y0 + fRadius * math.sin(angle) - nSIZE* math.sin(angle)  

	print(str(int(i)) +' '+ str(int(X)) +'  '+ str(int(Y)))

	sShapeName='ShapeString' + str(i+3).zfill(3)
	print(sShapeName)

	#FreeCAD.ActiveDocument.getObject(sShapeName).FontFile="C:/Users/sesa237770/Documents/Projects_DIY/002-24-hourclock/FONTS/Karla_BoldStencil.ttf"
	FreeCAD.ActiveDocument.getObject(sShapeName).FontFile="/home/pi/Documents/Projects_DIY/LaserFonts/Karla_BoldStencil.ttf"
	FreeCAD.ActiveDocument.getObject(sShapeName).Placement.Base=FreeCAD.Vector(X, Y, 0.0)
	FreeCAD.ActiveDocument.getObject(sShapeName).Size=nSIZE_LASER
	FreeCAD.ActiveDocument.getObject(sShapeName).String=str(int(i-1))+'  '+ str(int(angle_deg))
	FreeCAD.ActiveDocument.getObject(sShapeName).String=str(int(i-1))
	if (i==1):
		FreeCAD.ActiveDocument.getObject(sShapeName).String='24'
		FreeCAD.ActiveDocument.getObject(sShapeName).Placement.Base=FreeCAD.Vector(X-nSIZE, Y, 0.0)
		FreeCAD.ActiveDocument.getObject(sShapeName).Size=nSIZE_LASER*1.9
	if (i==6+1):
		FreeCAD.ActiveDocument.getObject(sShapeName).Size=nSIZE_LASER*1.9
	if (i==12+1):
		FreeCAD.ActiveDocument.getObject(sShapeName).Size=nSIZE_LASER*1.9
	if (i==18+1):
		FreeCAD.ActiveDocument.getObject(sShapeName).Size=nSIZE_LASER*1.9
		

#-------------------------------------------------------------------

App.activeDocument().recompute(None,True,True)
