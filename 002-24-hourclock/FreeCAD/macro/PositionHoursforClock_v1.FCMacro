import math

nSIZE=17
sNAME='ShapeString'
fRadius=130+5
X0=150 -nSIZE*0.8 +5
Y0=150 -nSIZE*0.8 + 5

#FreeCAD.ActiveDocument.getObject(sNAME).Size=nSIZE
XY={1: [8,0],2: [0,0],3: [0,0],4: [0,0],5: [0,0],6: [0,0],7: [0,0],8: [0,0],9: [0,0],10: [0,0],11: [0,0],12: [0,0]}
XY2={13: [0,0],14: [5,0],15: [0,0],16: [0,0],17: [0,0],18: [0,0],19: [0,0],20: [0,0],21: [0,0],22: [0,0],23: [0,0],24: [5,0],25: [0,0]}

XY.update(XY2)
#-------------------------------------------------------------------
for i in range(1, 25):

#	if (i>16):
#			nSIZE_LASER=nSIZE*0.8
#			#nSIZE_LASER=nSIZE*1.0
#	else:
#		nSIZE_LASER=nSIZE
	nSIZE_LASER=nSIZE



	angle_deg=-90 - (i-1)*15
	angle=angle_deg/180*3.14

	X=X0 + fRadius * math.cos(angle) - nSIZE* math.cos(angle) + XY[i][0]
	Y=Y0 + fRadius * math.sin(angle) - nSIZE* math.sin(angle)  + XY[i][1]

	print(str(int(i)) +' x:'+ str(int(X)) +'  y:'+ str(int(Y)))
	print(str(int(i)) +' dx:'+ str(int(xy[i][0])) +'  dy:'+ str(int(xy[i][1])))

	sShapeName='ShapeString' + str(i+3).zfill(3)
	print(sShapeName)

#	FreeCAD.ActiveDocument.getObject(sShapeName).FontFile="C:/Users/sesa237770/Documents/Projects_DIY/002-24-hourclock/FONTS/Karla_BoldStencil.ttf"
	FreeCAD.ActiveDocument.getObject(sShapeName).FontFile="/home/pi/Documents/Projects_DIY/002-24-hourclock/FONTS/Karla_BoldStencil.ttf"

	FreeCAD.ActiveDocument.getObject(sShapeName).Placement.Base=FreeCAD.Vector(X, Y, 0.0)
	FreeCAD.ActiveDocument.getObject(sShapeName).Size=nSIZE_LASER
	FreeCAD.ActiveDocument.getObject(sShapeName).String=str(int(i-1))+'  '+ str(int(angle_deg))


	FreeCAD.ActiveDocument.getObject(sShapeName).String=str(int(i-1))
	if ((i-1)>12):		
		FreeCAD.ActiveDocument.getObject(sShapeName).String=str(int(i-12-1))

	if (i==1):
		FreeCAD.ActiveDocument.getObject(sShapeName).String='24'
		FreeCAD.ActiveDocument.getObject(sShapeName).Placement.Base=FreeCAD.Vector(X-nSIZE, Y, 0.0)
		FreeCAD.ActiveDocument.getObject(sShapeName).Size=nSIZE_LASER*1.1

	if (i==6+1):
		FreeCAD.ActiveDocument.getObject(sShapeName).Size=nSIZE_LASER*1.1

	if (i==12+1):
		FreeCAD.ActiveDocument.getObject(sShapeName).Size=nSIZE_LASER*1.1

	if (i==18+1):
		FreeCAD.ActiveDocument.getObject(sShapeName).Size=nSIZE_LASER*1.1
		

#-------------------------------------------------------------------

App.activeDocument().recompute(None,True,True)
